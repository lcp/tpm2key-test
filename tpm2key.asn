--
-- TPM 2.0 key file format
--   to generate tpm2key_asn1_tab.c: asn1Parser tpm2key.asn
--
--   to generate a test DER: asn1Coding tpm2key.asn fake-key.asn1 -o fake-key.der
--
TPM2KEY {}
DEFINITIONS IMPLICIT TAGS ::=

BEGIN

TPMPolicy ::= SEQUENCE {
    CommandCode   [0] EXPLICIT INTEGER,
    CommandPolicy [1] EXPLICIT OCTET STRING
}

TPMAuthPolicy ::= SEQUENCE {
    Name    [0] EXPLICIT UTF8String OPTIONAL,
    Policy  [1] EXPLICIT SEQUENCE OF TPMPolicy
}

TPMKey ::= SEQUENCE {
    type        OBJECT IDENTIFIER,
    emptyAuth   [0] EXPLICIT BOOLEAN OPTIONAL,
    policy      [1] EXPLICIT SEQUENCE OF TPMPolicy OPTIONAL,
    secret      [2] EXPLICIT OCTET STRING OPTIONAL,
    authPolicy  [3] EXPLICIT SEQUENCE OF TPMAuthPolicy OPTIONAL,
    parent      INTEGER,
    pubkey      OCTET STRING,
    privkey     OCTET STRING
}

END
